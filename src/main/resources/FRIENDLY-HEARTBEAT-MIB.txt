-- 
-- FriendlyHeartbeat Java MIB 
--

FRIENDLY-HEARTBEAT-MIB DEFINITIONS ::= BEGIN

IMPORTS
    enterprises,
    MODULE-IDENTITY,
    OBJECT-TYPE,
    Unsigned32,
    NOTIFICATION-TYPE
        FROM SNMPv2-SMI
    DisplayString
        FROM SNMPv2-TC
    MODULE-COMPLIANCE, 
    OBJECT-GROUP,
    NOTIFICATION-GROUP
        FROM SNMPv2-CONF
    ;

-- Module Identity
------------------
friendlyMIB MODULE-IDENTITY 
    LAST-UPDATED "201004010000Z"    
    ORGANIZATION "FriendlySNMP"
    CONTACT-INFO "info@friendlysnmp.com"
    DESCRIPTION  "Heartbeat MIB supporting FriendlySNMP library"
    REVISION     "201004010000Z"    
    DESCRIPTION  "Initial revision"
    -- 1.3.6.1.4.1.29091.1.1
    ::= { friendlySNMP java(1) 1 }

-- Enterprise OIDs
------------------
friendlySNMP OBJECT IDENTIFIER ::= { enterprises 29091 }

-- Top-level tree (sections)
----------------------------
friendlyMIBObjects     OBJECT IDENTIFIER ::= { friendlyMIB 1 }
friendlyMIBConformance OBJECT IDENTIFIER ::= { friendlyMIB 3 }

--
-- Application Event and Scalars
--
appHeartbeat OBJECT IDENTIFIER ::= { friendlyMIBObjects 11 }
appTraps OBJECT IDENTIFIER ::= { appHeartbeat 0 }

heartbeat NOTIFICATION-TYPE
    STATUS  current
    DESCRIPTION "Application heartbeat notification"
    ::= { appTraps 1 }

heartbeatInterval OBJECT-TYPE
    SYNTAX      Unsigned32
    MAX-ACCESS  read-write
    STATUS      current
    DESCRIPTION 
        "The application SNMP agent sends heartbeat notifications at
         the interval specified in this scalar.  
         The valid range in Java terms is [0 .. Integer.MAX_VALUE].
         Setting this value to 0 disables heartbeat notifications."
    ::= { appHeartbeat 1 }

heartbeatStatus OBJECT-TYPE
    SYNTAX      DisplayString
    MAX-ACCESS  read-only
    STATUS      current
    DESCRIPTION 
        "This scalar is populated by application SNMP agent with 
         the application title, time passed since last heartbeat 
         notification and waiting time to next scheduled heartbeat 
         notification."
    ::= { appHeartbeat 2 }

--*************************
--***    Conformance    ***
--*************************
compliance MODULE-COMPLIANCE
    STATUS  current
    DESCRIPTION "The SNMP compliance section"
    MODULE  -- this module
    MANDATORY-GROUPS { 
        objectGroup,
        notifyGroup
    }
    ::= { friendlyMIBConformance 1 }

objectGroup OBJECT-GROUP
    OBJECTS {
        heartbeatInterval,
        heartbeatStatus
    }
    STATUS current
    DESCRIPTION "Scalar and columnar objects in this MIB"
    ::= { friendlyMIBConformance 2 }

notifyGroup NOTIFICATION-GROUP
    NOTIFICATIONS {
        heartbeat
    }
    STATUS current
    DESCRIPTION "Notifications in this MIB"
    ::= { friendlyMIBConformance 3 }

END
